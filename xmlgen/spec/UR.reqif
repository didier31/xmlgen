# UR

# Specification: Requirements Document
- ReqIF.Description: Requirements Document

## REQ-UR-1: Input

### REQ-UR-2
A xml template file represents the output by comprehension by :

#### REQ-UR-3
- its structure

#### REQ-UR-4
- inside which statements computing data to insert as content

### REQ-UR-5
An arbitrary number of input files gives all data requested by the statements.

## REQ-UR-6: Output

### REQ-UR-7
The xml template is expanded by data resulting of computing its statements, respecting an xml-schema.

## REQ-3
- its structure

## REQ-4
- inside which statements computing data to insert as content

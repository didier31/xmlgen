# Spec

# Specification: Requirements Document
- ReqIF.Description: Requirements Document

## REQ-SRS-1: Technologies

### REQ-SRS-2
The xml standard in the project is 1.1 ed. 2.
- Justification: The last proven release at this time.
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
## REQ-SRS-3: Embedded functional statements
- Justification: functional statements : statements returning data to insert.
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
### REQ-SRS-4
Processing needs are defined in process instructions according applied xml standard.
- Justification: process instructions in xml are instructions for external tools to xml.They can be inserted at any location dedicated to data.
  This is for these reasons this xml functionnality is really well suited.

### REQ-SRS-5
Data input files are referenced with a logical name.
- Justification: A logical name is a convenient way to reference different files.
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
### REQ-SRS-6
References to input data are read-only accessible by each functional statement.
- Justification: These references give input data to inject in output by the process instructions.
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
### REQ-SRS-7
These references are previously declared and available in the template-file's block of their declaration/definition only.
- Justification: This provision permits to store the value of a node to be used further in the template. This avoids bracktracking in input file.
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
### REQ-SRS-8
Statements return a string of characters or a list of strings of characters.
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
## REQ-SRS-9: Generation processing
- Justification: This topic specifies the behavior of process instructions
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
### REQ-SRS-10
Data collect is performed in one pass per file.
- Justification: Rewind in input data streams is no longer useful given the requirement, this one depends on.
  More, a data file may be twice or more as parameter with a different logical name.

### REQ-SRS-11
Data collect is performed by file forward-searches by type.

### REQ-SRS-12
It is triggered by a declaration in a process instruction.

### REQ-SRS-13
A predicate to satisfy can be optionnally added to this kind of search.

#### REQ-SRS-14
This kind of search can be optionnally limited to a data block. By default, it is performed on the whole file.

#### REQ-SRS-15
The data collect acts like an iterative loop, searching forward the next data of specified type, in the specified file.

##### REQ-SRS-16
This data is referencable via a declared logical name.

##### REQ-SRS-17
The scope of the declaration is limited to the current block.

##### REQ-SRS-18
The process deduces the expected data presentation in the output file according the result's type of a processing instruction and the xsd structure of the part of template whom the processing instruction belongs to.
- Justification: An implicit arrangement like this one is a convenient solution for the user.
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
##### REQ-SRS-19
If the dataset is empty, no insertion is performed.
- Justification: Trivial.

##### REQ-SRS-20
If dataset is a singleton, the value of the unique data-element is inserted in place of the process instruction.
- Justification: Trivial.

##### REQ-SRS-21
Elements are laid out in rows if no column following or while next columns are empty in the template in the limit of the number of columns. A new row is then created to insert next data-elements if its insertion should override a cell already filled with data or overshots the number of columns.
- Justification: This convention is an intuitive way to map a list of data to a grid.

# Software Reliability Specification

# Specification: Requirements Document
- ReqIF.Description: Requirements Document

## REQ-1: User input checks

### REQ-7
Check that each data source is readable.
- Consequence: ALTERATION
- Justification: If a data source is not readable, default values can then be produced nevertheless, according xml-schema.

## REQ-2
Check that an xml-schema is associated with xml template.
- Consequence: TOTAL LOSS
- Justification: Without structural information, no xml expansion is possible.

## REQ-3
Check syntactic correctness of the statements handling data sources.
- Consequence: ALTERATION

### REQ-4
Check that an iterated captured data is a list.
- Consequence: ALTERATION

### REQ-5
Check that data to insert are representable by a string of characters.
- Consequence: ALTERATION

#### REQ-6
Check that output is writable.
- Consequence: TOTAL LOSS

### REQ-8
Check that each value, inserted in output conforms the related xml-schema.
- Consequence: ALTERATION
- Justification: If a data doesn't conform, default values can then be produced,nevertheless, according xml-schema.

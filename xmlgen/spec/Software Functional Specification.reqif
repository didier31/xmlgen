# Spec

# Specification: Requirements Document
- ReqIF.Description: Requirements Document

## REQ-SRS-1: Technologies (Requirement Type)

### REQ-SRS-2 (Requirement Type)
The xml standard, used is 1.1 ed. 2.
- Justification: The last proven release at this time.
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
### REQ-SRS-41 (Requirement Type)
Acceleo Query Language (TBD: version) is the data language for capture filtering and generation.
- SpecRealtion Type -> REQ-SRS-13

## REQ-SRS-9: Generation processing (Requirement Type)
- Justification: This topic specifies the semantics of process instructions.

### R43 (Note)
Generation of the xml ouput is based on an xml template with embedded generation instructions as described in this section.

### REQ-SRS-53 (Requirement Type)
Data sources are EMF resources.
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
### REQ-SRS-28 (Requirement Type)
A generation processing is composed by two kinds of processing :

#### REQ-SRS-29 (Requirement Type)
- the capture of data from a data source,
- Justification: A stage of data filtering in order to get useful data to handle.
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- SpecRealtion Type -> REQ-SRS-30
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
#### REQ-SRS-30 (Requirement Type)
- the insertion of captured data (or part of) in output.

### REQ-SRS-44 (Requirement Type)
These instructions are inserted in process instructions blocks conforming to the xml standard.
- Justification: This provision allows to insert generation instructions exactly at the place the data must be inserted and data structure, expanded.
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
### REQ-SRS-37 (Requirement Type)
Data capture
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
#### REQ-SRS-13 (Requirement Type)
The capture of data is performed according a filtering criteria, in a turing-complete capable language.
- Justification: It enables to extract interesting data to insert.

#### REQ-SRS-31 (Requirement Type)
The scope of capture is :

##### REQ-SRS-32 (Requirement Type)
- the data source
- Justification: Trivial.

##### REQ-SRS-33 (Requirement Type)
- or a part of it
- Justification: It enables efficiency of capture.

##### REQ-SRS-54 (Requirement Type)
A special keyword enables list-item individual selection. It triggers an iteration through a list on the current xml output block.
- Justification: This provision seems to be necessary in order to perform iteration on lists.

#### REQ-SRS-38 (Requirement Type)
References to captured data

##### REQ-SRS-51 (Requirement Type)
A user-defined logical name is associated with the whole content of each data source.
- Justification: These names are the root access to get data from the datasource.
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
###### REQ-SRS-52 (Requirement Type)
It is defined for the overall generation processing.

##### REQ-SRS-6 (Requirement Type)
An user-defined logicial name is associated to each resulting captured data. This connection is called a definition.
- Justification: This name is used in the different kinds of processing, composing generation process.

##### REQ-SRS-7 (Requirement Type)
The life cycle of the logical name's definition (i.e its related captured data) is limited to the xml container xml whose its declaration is part of.

##### REQ-SRS-34 (Requirement Type)
Same logical name can be reused :
- Justification: This convention is usual in programming languages. Users who are most of them programmers are thus aware of this convention.

###### REQ-SRS-35 (Requirement Type)
- at same xml level, a new definition replaces the previous one.

###### REQ-SRS-36 (Requirement Type)
- in an inner xml level, a new definition hides the previous one. The previous definition is restored when the new one comes to end of life (i.e becomes undefined).

#### REQ-SRS-39 (Requirement Type)
Statements for generation
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
##### REQ-SRS-40 (Requirement Type)
Statements are expressed in a turing-complete language.
- Justification: Required for an obvious reason of computing capability.

##### REQ-SRS-43 (Requirement Type)
Logical names of captured data are used in statements as actual arguments.
- Justification: Trivial.

##### REQ-SRS-8 (Requirement Type)
Statements return a value or a list provided with a character string representation.
- Justification: This requirement allows statements to return any data of any type provided they are printable.

##### REQ-SRS-46 (Requirement Type)
Data Layout

###### R51 (Note)
The process deduces the expected data presentation in the output file according the result's type of a processing instruction as follows.
- Justification: An implicit arrangement like this one is a convenient solution for the user.

###### REQ-SRS-18 (Requirement Type)
The process conforms to the xsd structure, specially at xml-expanding.
- Justification: Trivial.

###### REQ-SRS-19 (Requirement Type)
If the dataset is empty, no insertion is performed.
- Justification: Trivial.

###### REQ-SRS-20 (Requirement Type)
If dataset is a singleton, the value of the unique data-element is inserted in place of the process instruction.
- Justification: Trivial.

###### REQ-SRS-47 (Requirement Type)
Layout of data lists

###### REQ-SRS-21 (Requirement Type)
List elements are laid out as follows :
- Justification: This convention is an intuitive way to map a list of data to a grid.

###### REQ-SRS-48 (Requirement Type)
- in rows if no column following or while next columns are empty in the template in the limit of the number of columns.

###### REQ-SRS-49 (Requirement Type)
- A new row is created to insert next data-elements if its insertion should override a cell already filled with data or overshots the number of columns.

## REQ-SRS-4 (Requirement Type)
Processing needs are defined in process instructions according applied xml standard.
- Justification: process instructions in xml are instructions for external tools to xml. Process instructions can be inserted at any location dedicated to data.
  This is for these reasons this xml functionnality is really well suited.

## REQ-SRS-5 (Requirement Type)
The whole content of data input files are referenced with a user-defined logical name.
- Justification: A logical name is a convenient way to reference different files.

## REQ-SRS-11 (Requirement Type)
Data search is performed according user-defined criteria.

## REQ-SRS-12 (Requirement Type)
Data collect is triggered by declaration in a process instruction.

## REQ-SRS-14 (Requirement Type)
- a data block only.

## REQ-SRS-15 (Requirement Type)
Data search collects data in the order they appears in the input file structure.

## REQ-SRS-16 (Requirement Type)
Each item of this list is referencable via a declared logical name.

## REQ-SRS-17 (Requirement Type)
The like cycle of the declaration and so, related data is limited to the current block.

## REQ-SRS-24 (Requirement Type)

## REQ-SRS-25 (Requirement Type)
This search can be performed on either :

## REQ-SRS-26 (Requirement Type)
- a whole file.

## REQ-SRS-27 (Requirement Type)
These data are collected in a list.

## REQ-SRS-42 (Requirement Type)
EMF's version of data sources, used is 2.9.

## REQ-SRS-45 (Requirement Type)

## R42 (Note)
Generation of the xml ouput is based on an xml template with embedded generation instructions.
